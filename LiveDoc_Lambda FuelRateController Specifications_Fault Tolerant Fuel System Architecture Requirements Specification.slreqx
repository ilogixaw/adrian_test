# LiveDoc_Lambda FuelRateController Specifications_Fault Tolerant Fuel System Architecture Requirements Specification

## https://lambda-latest.net.plm.eds.com/polarion/#/project/FuelRateController/wiki/Specifications/Fault Tolerant Fuel System Architecture Requirements Specification: References to Fault Tolerant Fuel System Architecture Requirements Specification (Container)
Read-only references to Polarion Workitem document.

### FRC-141: Main Sub Systems (Container)

#### FRC-167: Airflow (Container)

##### FRC-143: Mass airflow estimation (Airflow calculation) ***UPDATED*** (Functional)
The controller will use engine speed, throttle position and manifold pressure to estimate the mass airflow through the engine.
| Engine AirFlow (kg/h) | Engine Speed (rpm) |
| --- | --- |
| 8 | 500 |
| 11 | 1000 |
| 18 | 1500 |
| 23 | 2000 |
| 29 | 2500 |

#### FRC-170: Sensor Correction and Fault Redundancy (Container)

##### FRC-151: Fault Redundancy (Functional)
The controller shall provide fault redundancy monitoring and failure detection when operating.

##### FRC-262: New requirement (Functional)

#### FRC-168: Pumping Constant (Container)

##### FRC-145: Determination of pumping efficiency (Pumping Constant) (Functional)
The airflow calculation will use a calibratable table to determine the pumping efficiency of the engine based on engine speed and manifold pressure.

#### FRC-171: Airflow Integrator (Container)

##### FRC-147: Adjustment of estimated airflow (Airflow calculation/Integrator) (Functional)
The fuel system will use an exhaust gas oxygen sensor to adjust the estimated airflow

#### FRC-169: Failure Control Vector (Container)

##### FRC-149: Failure Control Vector (Functional)
The controller shall provide access to the internal vector of failure flags that indicate what sensors are in a failure condition.

### FRC-152: Failure Management Subsystem (Container)

#### FRC-173: Fault monitoring and detection (Container)

##### FRC-153: Fault Monitoring (Functional)
The fuel rate controller logic shall monitor faults relating too O2 oxygen, Manifold Pressure and Throttle sensors.

##### FRC-165: Fault Detection (Functional)
The system shall be able to detect if one or multiple sensors fail.

##### FRC-155: Oxygen sensor disabled during warmup (Functional)
During a calibratable warm up period the oxygen sensor correction will be disabled.

##### FRC-157: Enriched mixture usage (Functional)
The fuel system will use an enriched mixture whenever a sensor has failed.

#### FRC-172: Disable Fuel system (Container)
| Property Name | Property Value |
| --- | --- |
| Parameters |  |
| Path | FuelSysWithReqLinks/fuel rate controller/control logic/Fueling_Mode |
| Id | 70 |
| SSIdNumber | 22 |
| Name | Fuel_Disabled |
| Description | The fuel is completely shut off while in this state. |
| LabelString | Fuel_Disabled entry: fuel_mode = DISABLED |
| FontSize | 13.54 |
| ArrowSize | 12 |
| TestPoint | false |
| BadIntersection | false |
| Document |  |
| Tag |  |
| RequirementInfo |  |
| ExecutionOrder | 0 |
| ContentPreviewEnabled | false |
| Position | 676.05 595.258 241.534 298.801 |
| Decomposition | EXCLUSIVE_OR |
| Type | OR |
| IsSubchart | false |
| IsGrouped | false |
| InlineOption | Auto |
| HasOutputData | false |
| OutputData |  |
| OutputMonitoringMode | ChildActivity |
| IsExplicitlyCommented | false |
| IsImplicitlyCommented | false |
| CommentText |  |

##### FRC-161: Disable fuel system due to sensor failure (Functional)
The fuel system will disable fuel when two or more sensors have failed to prevent the possibility of fire.

##### FRC-163: Disable fuel system due to engine speed (Functional)
The fuel system will disable fuel whenever the engine speed exceeds the calibratable threshold.
